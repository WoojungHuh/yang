module ieee802-dot1q-ats-bridge {
  yang-version "1.1";
  namespace urn:ieee:std:802.1Q:yang:ieee802-dot1q-ats-bridge;
  prefix ats-bridge;
  import ietf-interfaces {
    prefix if;
  }
  import ieee802-dot1q-bridge {
    prefix dot1q;
  }
  import ieee802-dot1q-ats {
    prefix ats;
  }
  import ieee802-dot1q-stream-filters-gates {
    prefix sfsg;
  }
  organization
    "IEEE 802.1 Working Group";
  contact
    "WG-URL: http://ieee802.org/1/
    WG-EMail: stds-802-1-l@ieee.org
    
    Contact: IEEE 802.1 Working Group Chair
    Postal: C/O IEEE 802.1 Working Group
            IEEE Standards Association
            445 Hoes Lane
            Piscataway, NJ 08854
            USA
    
    E-mail: stds-802-1-chairs@ieee.org";
  description
    "This module provides management of IEEE 802.1Q Bridge components
    that support Asynchronous Traffic Shaping (ATS).
    
    Copyright (C) IEEE (2023).
    
    This version of this YANG module is part of IEEE Std 802.1Q; see the
    standard itself for full legal notices.";

  revision 2026-11-04 {
    description
      "Fix of Maintenance 0392 for ieee802-dot1q-ats-bridge";
    reference
      "IEEE Std 802.1Qcz-2023, Bridges and Bridged Networks - Congestion
      Isolation.";
  }

  revision 2023-07-03 {
    description
      "Published as part of IEEE Std 802.1Qcz-2023.";
    reference
      "IEEE Std 802.1Qcz-2023, Bridges and Bridged Networks - Congestion
      Isolation.";
  }
  augment "/if:interfaces/if:interface/dot1q:bridge-port" {
    description
      "Augments Bridge Ports by ATS per-Port parameters.";
    uses ats:ats-port-parameters;
  }
  augment "/dot1q:bridges/dot1q:bridge/dot1q:component" {
    description
      "Augments the Bridge component with ATS parameters.";
    uses ats:ats-parameters;
    uses sfsg:sfsg-parameters {
      augment "stream-filters/stream-filter-instance-table" {
        description
          "Augments the Bridge component stream filter for ATS
          schedulers.";

        container scheduler {
          description
            "This container encapsulates ATS scheduler nodes.";
          leaf scheduler-ref {
            type leafref {
              path
                '..'+
                '/..'+
                '/..'+
                '/..'+
                '/schedulers'+
                '/scheduler-instance-table'+
                '/scheduler-instance-id';
            }
            description
              "A reference to the ATS scheduler associated with this
              stream filter.";
          }
          leaf scheduler-enable {
            type boolean;
            default "false";
            description
              "If TRUE, this stream filter has an associated ATS
              scheduler referenced by scheduler-ref. If FALSE, no ATS
              scheduler is associated with this stream filter
              (scheduler-ref is ignored).";
          }
        }
      }
    }
  }
}
