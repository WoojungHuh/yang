module ieee802-dot1q-stream-filters-gates-sys {
  yang-version "1.1";
  namespace
    urn:ieee:std:802.1Q:yang:ieee802-dot1q-stream-filters-gates-sys;
  prefix sfsg-sys;
  import ietf-system {
    prefix sys;
  }
  import ieee802-dot1q-stream-filters-gates {
    prefix sfsg;
  }
  organization
    "IEEE 802.1 Working Group";
  contact
    "WG-URL: https://1.ieee802.org/
    WG-EMail: stds-802-1@ieee.org
    Contact: IEEE 802.1 Working Group Chair
    Postal: C/O IEEE 802.1 Working Group
           IEEE Standards Association
           445 Hoes Lane
           Piscataway, NJ 08855
           USA
    
    E-mail: STDS-802-1-CHAIRS@LISTSERV.IEEE.ORG";
  description
    "This module provides management of General Frame Quality of Service
    (GFQoS) systems that support Stream Filters and Stream Gates.
    
    Copyright (C) IEEE (2026).
    
    This version of this YANG module is part of IEEE Std 802.1DC; see the
    standard itself for full legal notices.";
  revision 2026-06-03 {
    description
      "Maintenance #0393.";
    reference
      "IEEE Std 802.1DC-2023";
  }
  augment "/sys:system" {
    description
      "Augments the System with stream filters and stream
      gates.";
    uses sfsg:sfsg-parameters;
  }
}
